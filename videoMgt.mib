VIDEO-MIB DEFINITIONS ::= BEGIN

IMPORTS
        enterprises
                FROM RFC1155-SMI;

myCompany            OBJECT IDENTIFIER ::= { enterprises 12619 }
END



NEW-MIB DEFINITIONS ::= BEGIN

IMPORTS
	TimeTicks
		FROM RFC1155-SMI
	OBJECT-TYPE
		FROM RFC-1212
	myCompany
		FROM VIDEO-MIB;

videoMgr             OBJECT IDENTIFIER ::= { myCompany 1 }

vmUptime  OBJECT-TYPE
	SYNTAX     TimeTicks
	ACCESS     read-only
	STATUS     mandatory
	DESCRIPTION 
		"Timeticks desde que o sistema foi inicializado"
	::= { videoMgr 1 }

vmProcessCount  OBJECT-TYPE
	SYNTAX     INTEGER (0..255)
	ACCESS     read-write
	STATUS     mandatory
	DESCRIPTION 
		"Número de processos executando o sistema."
	::= { videoMgr 2 }

vmProcessTable  OBJECT-TYPE
	SYNTAX SEQUENCE OF VmProcessEntry
	ACCESS     not-accessible
	STATUS     mandatory
	DESCRIPTION 
		"Tabela dos processos que estão respondendo requisições do sistema."
	::= { videoMgr 3 }

vmProcessEntry  OBJECT-TYPE
	SYNTAX 	VmProcessEntry
	ACCESS     not-accessible
	STATUS     mandatory
	DESCRIPTION 
		""
	INDEX { vmProcessIndex }
	::= { vmProcessTable 1 }

VmProcessEntry ::= SEQUENCE {
	vmProcessIndex
		INTEGER,
	vmProcessPID
		INTEGER,
	vmProcessOwner
		OCTET STRING,
	vmProcessCPU
		INTEGER,
	vmProcessMem
		INTEGER,
	vmProcessState
		OCTET STRING
}

vmProcessIndex  OBJECT-TYPE
	SYNTAX     INTEGER
	ACCESS     read-only
	STATUS     mandatory
	DESCRIPTION 
		"Indice do processo na tabela"
	::= { vmProcessEntry 1 }

vmProcessPID  OBJECT-TYPE
	SYNTAX     INTEGER
	ACCESS     read-only
	STATUS     mandatory
	DESCRIPTION 
		"PID do processo"
	::= { vmProcessEntry 2 }

vmProcessOwner  OBJECT-TYPE
	SYNTAX     OCTET STRING
	ACCESS     read-only
	STATUS     mandatory
	DESCRIPTION 
		"Owner do processo"
	::= { vmProcessEntry 3 }

vmProcessCPU  OBJECT-TYPE
	SYNTAX     INTEGER (0..100)
	ACCESS     read-only
	STATUS     mandatory
	DESCRIPTION 
		"%CPU usado pelo processo"
	::= { vmProcessEntry 4 }

vmProcessMem  OBJECT-TYPE
	SYNTAX     INTEGER (0..100)
	ACCESS     read-only
	STATUS     mandatory
	DESCRIPTION 
		"%Memória usado pelo sistema"
	::= { vmProcessEntry 5 }

vmProcessState  OBJECT-TYPE
	SYNTAX     OCTET STRING
	ACCESS     read-only
	STATUS     mandatory
	DESCRIPTION 
		"Estado do processo na nomenclatura Unix."
	::= { vmProcessEntry 6 }

vmChannelTable  OBJECT-TYPE
	SYNTAX SEQUENCE OF VmChannelEntry
	ACCESS     not-accessible
	STATUS     mandatory
	DESCRIPTION 
		"Tabela dos canais existentes no sistema."
	::= { videoMgr 4 }

vmChannelEntry  OBJECT-TYPE
	SYNTAX 	VmChannelEntry
	ACCESS     not-accessible
	STATUS     mandatory
	DESCRIPTION 
		""
	INDEX { vmChannelId }
	::= { vmChannelTable 1 }

VmChannelEntry ::= SEQUENCE {
	vmChannelId
		INTEGER,
	vmChannelAudience
		INTEGER
}

vmChannelId  OBJECT-TYPE
	SYNTAX     INTEGER
	ACCESS     read-only
	STATUS     mandatory
	DESCRIPTION 
		"Id do Canal."
	::= { vmChannelEntry 1 }

vmChannelAudience  OBJECT-TYPE
	SYNTAX     INTEGER
	ACCESS     read-only
	STATUS     mandatory
	DESCRIPTION 
		"Audiência do canal."
	::= { vmChannelEntry 2 }

vmVideoTable  OBJECT-TYPE
	SYNTAX SEQUENCE OF VmVideoEntry
	ACCESS     not-accessible
	STATUS     mandatory
	DESCRIPTION 
		"Tabela dos videos existentes no sistema."
	::= { videoMgr 5 }

vmVideoEntry  OBJECT-TYPE
	SYNTAX 	VmVideoEntry
	ACCESS     not-accessible
	STATUS     mandatory
	DESCRIPTION 
		""
	INDEX { vmVideoId }
	::= { vmVideoTable 1 }

VmVideoEntry ::= SEQUENCE {
	vmVideoId
		INTEGER,
	vmVideoAudience
		INTEGER,
	vmVideoAdvertisingMetrics
		INTEGER,
	vmVideoKindVOD
		INTEGER,
	vmVideoKindLive
		INTEGER
}

vmVideoId  OBJECT-TYPE
	SYNTAX     INTEGER
	ACCESS     read-only
	STATUS     mandatory
	DESCRIPTION 
		"Id do vídeo."
	::= { vmVideoEntry 1 }

vmVideoAudience  OBJECT-TYPE
	SYNTAX     INTEGER
	ACCESS     read-only
	STATUS     mandatory
	DESCRIPTION 
		"Numero de visitações do video."
	::= { vmVideoEntry 2 }

vmVideoAdvertisingMetrics  OBJECT-TYPE
	SYNTAX     INTEGER
	ACCESS     read-write
	STATUS     mandatory
	DESCRIPTION 
		"Prioridade de propaganda no vídeo."
	::= { vmVideoEntry 3 }

vmVideoKindVOD  OBJECT-TYPE
	SYNTAX     INTEGER (0..1)
	ACCESS     read-only
	STATUS     mandatory
	DESCRIPTION 
		"Tipo de vídeo VOD."
	::= { vmVideoEntry 4 }

vmVideoKindLive  OBJECT-TYPE
	SYNTAX     INTEGER (0..1)
	ACCESS     read-only
	STATUS     mandatory
	DESCRIPTION 
		"Tipo de vídeo Live."
	::= { vmVideoEntry 5 }

vmBlockedCountriesTable  OBJECT-TYPE
	SYNTAX SEQUENCE OF VmBlockedCountriesEntry
	ACCESS     not-accessible
	STATUS     mandatory
	DESCRIPTION 
		"Tabela de países proibidos de acessar o sistema."
	::= { videoMgr 6 }

vmBlockedCountriesEntry  OBJECT-TYPE
	SYNTAX 	VmBlockedCountriesEntry
	ACCESS     not-accessible
	STATUS     mandatory
	DESCRIPTION 
		""
	INDEX { vmBlockedCountrieName }
	::= { vmBlockedCountriesTable 1 }

VmBlockedCountriesEntry ::= SEQUENCE {
	vmBlockedCountrieName
		OCTET STRING
}

vmBlockedCountrieName  OBJECT-TYPE
	SYNTAX     OCTET STRING (SIZE(2))
	ACCESS     read-write
	STATUS     mandatory
	DESCRIPTION 
		"Código do país. Ex. BR."
	::= { vmBlockedCountriesEntry 1 }
END

-- This MIB was created using NuDesign Technologies' Visual MIBuilder (Ver 5.2).
