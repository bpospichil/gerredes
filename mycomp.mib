VIDEO-MIB DEFINITIONS ::= BEGIN

IMPORTS
	enterprises
		FROM RFC1155-SMI;

myCompany            OBJECT IDENTIFIER ::= { enterprises 12619 }
END

-- This MIB was created using NuDesign Technologies' Visual MIBuilder (Ver 5.2).
